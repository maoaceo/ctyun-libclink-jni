-- Clink-MIB.txt
    Clink-MIB DEFINITIONS ::= BEGIN
 
        IMPORTS
            OBJECT-GROUP, MODULE-COMPLIANCE, NOTIFICATION-GROUP    
                FROM SNMPv2-CONF    
            enterprises, Integer32, Unsigned32, OBJECT-TYPE, MODULE-IDENTITY, 
            NOTIFICATION-TYPE    
                FROM SNMPv2-SMI    
            DisplayString    
                FROM SNMPv2-TC;
    
-- October 09, 2002 at 14:50 GMT
        -- 1.3.6.1.4.1.2699
        pwg MODULE-IDENTITY 
            LAST-UPDATED "202304252100Z"        -- Apirl 25, 2023 at 21:00 GMT
            ORGANIZATION 
                "Ctyun"  
            CONTACT-INFO 
                ""  
            DESCRIPTION 
                "Shared USB Printer MIB."
            ::= { enterprises 2699 }
    
--  Node definitions
-- This part will include all details about the Test.
        -- 1.3.6.1.4.1.2699.1
        mibs OBJECT IDENTIFIER ::= { pwg 1 } 
 
    
        -- .1.3.6.1.4.1.2699.1.2.1.2.1.1.3.1
        ppmPrinterIEEE1284DeviceId OBJECT-TYPE
            SYNTAX DisplayString (SIZE (0..100))
            MAX-ACCESS read-only
            STATUS current
            DESCRIPTION
                ""
            ::= { mibs 1 }
    END
 
-- Clink-MIB.txt
